Seq4 DEFINITIONS ::=
BEGIN
S1 ::= SEQUENCE { }
S2 ::= SEQUENCE {...}
S3 ::= SEQUENCE {... !5}
S4 ::= SEQUENCE {..., ... }
S5 ::= SEQUENCE { ... !5, ... }




S6 ::= SEQUENCE { i1 INTEGER, i2 INTEGER }
S7 ::= SEQUENCE { i1 INTEGER, i2 INTEGER, ...   }
S8 ::= SEQUENCE { i1 INTEGER, i2 INTEGER, ... , e1 INTEGER, e2 INTEGER  }
S9 ::= SEQUENCE { i1 INTEGER, i2 INTEGER, ... , e1 INTEGER, [[e3 INTEGER ]]  }
S10 ::= SEQUENCE { i1 INTEGER, i2 INTEGER, ... !5   }
S11 ::= SEQUENCE { i1 INTEGER, i2 INTEGER, ... !5, e1 INTEGER, e2 INTEGER  }
S12 ::= SEQUENCE { i1 INTEGER, i2 INTEGER, ... !5, e1 INTEGER, [[e3 INTEGER ]]  }
S13 ::= SEQUENCE { i1 INTEGER, i2 INTEGER, ...  , ... }
S14 ::= SEQUENCE { i1 INTEGER, i2 INTEGER, ... , e1 INTEGER, e2 INTEGER, ... }
S15 ::= SEQUENCE { i1 INTEGER, i2 INTEGER, ... , e1 INTEGER, [[e3 INTEGER ]], ... }
S16 ::= SEQUENCE { i1 INTEGER, i2 INTEGER, ... !5, ... }
S17 ::= SEQUENCE { i1 INTEGER, i2 INTEGER, ... !5, e1 INTEGER, e2 INTEGER, ... }
S18 ::= SEQUENCE { i1 INTEGER, i2 INTEGER, ... !5, e1 INTEGER, [[e3 INTEGER ]], ... }
S19 ::= SEQUENCE { i1 INTEGER, i2 INTEGER, ...  , ... , i3 INTEGER, i4 INTEGER }
S20 ::= SEQUENCE { i1 INTEGER, i2 INTEGER, ... , e1 INTEGER, e2 INTEGER, ... , i3 INTEGER, i4 INTEGER }
S21 ::= SEQUENCE { i1 INTEGER, i2 INTEGER, ... , e1 INTEGER, [[e3 INTEGER ]], ... , i3 INTEGER, i4 INTEGER }
S22 ::= SEQUENCE { i1 INTEGER, i2 INTEGER, ... !5, ... , i3 INTEGER, i4 INTEGER }
S23 ::= SEQUENCE { i1 INTEGER, i2 INTEGER, ... !5, e1 INTEGER, e2 INTEGER, ... , i3 INTEGER, i4 INTEGER }
S24 ::= SEQUENCE { i1 INTEGER, i2 INTEGER, ... !5, e1 INTEGER, [[e3 INTEGER ]], ... , i3 INTEGER, i4 INTEGER }
S25 ::= SEQUENCE { ...  , ... , i3 INTEGER, i4 INTEGER }
S26 ::= SEQUENCE { ... , e1 INTEGER, e2 INTEGER, ... , i3 INTEGER, i4 INTEGER }
S27 ::= SEQUENCE { ... , e1 INTEGER, [[e3 INTEGER ]], ... , i3 INTEGER, i4 INTEGER }
S28 ::= SEQUENCE { ... !5, ... , i3 INTEGER, i4 INTEGER }
S29 ::= SEQUENCE { ... !5, e1 INTEGER, e2 INTEGER, ... , i3 INTEGER, i4 INTEGER }
S30 ::= SEQUENCE { ... !5, e1 INTEGER, [[e3 INTEGER ]], ... , i3 INTEGER, i4 INTEGER }
S31 ::= SEQUENCE { ...   }
S32 ::= SEQUENCE { ...  , ... }
S33 ::= SEQUENCE { ... , e1 INTEGER, e2 INTEGER  }
S34 ::= SEQUENCE { ... , e1 INTEGER, [[e3 INTEGER ]]  }
S35 ::= SEQUENCE { ... , e1 INTEGER, e2 INTEGER, ... }
S36 ::= SEQUENCE { ... , e1 INTEGER, [[e3 INTEGER ]], ... }
S37 ::= SEQUENCE { ... !5   }
S38 ::= SEQUENCE { ... !5, ... }
S39 ::= SEQUENCE { ... !5, e1 INTEGER, e2 INTEGER  }
S40 ::= SEQUENCE { ... !5, e1 INTEGER, [[e3 INTEGER ]]  }
S41 ::= SEQUENCE { ... !5, e1 INTEGER, e2 INTEGER, ... }
S42 ::= SEQUENCE { ... !5, e1 INTEGER, [[e3 INTEGER ]], ... }
END
