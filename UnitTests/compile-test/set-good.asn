Set1 DEFINITIONS EXPLICIT TAGS ::=
BEGIN

S1 ::= SET {
    i1 INTEGER,
    i2 [1] INTEGER
}

a S1 ::= {i1 5, i2 7}
b S1 ::= {i2 10, i1 1}

S2 ::= SET {
     i1 INTEGER,
     s1 SET {
       i1 INTEGER,
       b1 BOOLEAN
    }
}

c S2 ::= {i1 1, s1 {i1 11, b1 TRUE }}

S3 ::= SET {
    i1 INTEGER,
    s1 S1
}

d S3 ::= {i1 1, s1 a}

e S3 ::= {i1 1, s1 {i1 11, i2 12 } }


S4 ::= SET {
     i1 INTEGER,
     i2 [1] INTEGER OPTIONAL,
     b1 BOOLEAN
}

f S4 ::= {i1 1, i2 2, b1 TRUE }

g S4 ::= {i1 1, b1 FALSE }

S5 ::= SET {
    i1 INTEGER,
    i2 [1] INTEGER DEFAULT 3,
    b1 BOOLEAN
}

i S5 ::= {i1 1, i2 2, b1 TRUE }

j S5 ::= {i1 1, i2 3, b1 FALSE }

k S5 ::= {i1 1, b1 TRUE }

END
