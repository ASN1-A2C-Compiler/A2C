BitString1 DEFINITIONS EXPLICIT TAGS ::=
BEGIN

a INTEGER ::= 1

T0 ::= BIT STRING

T1 ::= BIT STRING { a(2) }

T2 ::= BIT STRING { a(3), b(a) }

c T2 ::= 'A'H

d T2 ::= '101'B

e T2 ::= { }

f T2 ::= {a}

g T2 ::= {a,b}

h T0 ::= 'A0C'H

i T0 ::= '1010101000'B

T3 ::= BIT STRING { a(3), b(0), c(1) }

a1 INTEGER ::= a

T4 ::= BIT STRING { a1(a1) }

-- Missing a CONTAINING test

END
